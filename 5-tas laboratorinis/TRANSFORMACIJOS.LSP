perkelimo transformacijos matrica
(defun c:perkelimas(/ x1 y1 x2 y2 x3 y3 xx1 yy1 xx2 yy2 xx3 yy3 xxx1 yyy1 xxx2 yyy2
	    x y m11 m12 m13 m21 m22 m23 m31 m32 m33 TX TY perkelimass)
(setq x1 2 y1 6 x2 6 y2 10 x3 6 y3 2)
(command "color" "Red" )
(setq variantas1 (getint "\nNurodykite varianta - iveskite destytojo nurodyta numeri: "))
(setq perkelimass (rem variantas1 11))

  (if (= perkelimass 0) (setq TX 6 TY 4)) (if (= perkelimass 1) (setq TX 8 TY 6))
  (if (= perkelimass 2) (setq TX 8 TY 8)) (if (= perkelimass 3) (setq TX 6 TY 6))
  (if (= perkelimass 4) (setq TX 9 TY 10)) (if (= perkelimass 5) (setq TX 7 TY 8))
  (if (= perkelimass 6) (setq TX 10 TY 7)) (if (= perkelimass 7) (setq TX 6 TY 7))
  (if (= perkelimass 8) (setq TX 7 TY 0)) (if (= perkelimass 9) (setq TX 8 TY 1))
  (if (= perkelimass 10) (setq TX 7 TY 5))
  (setq xx1 (+ x1 TX) yy1 (+ y1 TY) xx2 (+ x2 TX) yy2 (+ y2 TY) xx3 (+ x3 TX) yy3 (+ y3 TY))
(command "ucsicon" "off")  (command "limits" (list -2 -2) (list 21 21))
(command "zoom" "window" (list -2 -2) (list 21 21) )
(command "grid" 1) (command "grid" "on")
(command "snap" 1) (command "snap" "off") (setvar "osmode" 0)
(command "erase" "all" "") (command "color" "Red" )
(command "line" '(-1 0) '(20 0) "") (command "line" '(0 -1) '(0 20) "")
(command "pline" '(19 0) "w" 0.5 0 '(20 0) "")
(command "pline" '(0 19) "w" 0.5 0 '(0 20) "")
(setvar "pdmode" 2) (setvar "pdsize" -4)
(setq x 1) (setq y 1) (command "color" "Magenta" )
(command "point" (list x1 y1)) (command "point" (list xx1 yy1)) 
(repeat 18 (command "point" (list 0 y)(command "point" (list x 0))  )
  (setq x (+ x 1)) (setq y (+ y 1)))
  (setq x 2) (setq y 2) (command "color" "Blue" )
(repeat 9 (command "text" "j" "mc" (list -1 y) 0.5 0 X)
  (command "text" "j" "c" (list x -1) 0.5 0 y)
  (setq x (+ x 2)) (setq y (+ y 2)))
(command "line" (list x1 y1) (list x2 y2) (list x3 y3) "c") (command "color" "Green" )
(command "line" (list xx1 yy1) (list xx2 yy2) (list xx3 yy3) "c")
(command "color" "Red" )
(command "text" "j" "mc"(list (+ x1 2) y1)  0.8 0 "Yra")
(command "text" "j" "mc"(list (+ xx1 2) yy1)  0.6 0 "Reikia")
(prompt "\nIveskite perkelimo transformacijos matricos 1-os eilutes elementus:")
  (setq M11 (getreal "\n1-ojo elemento reiksme: "))
  (setq M12 (getreal "2-ojo elemento reiksme: "))
  (setq M13 (getreal "3-ojo elemento reiksme: "))
(prompt "\nIveskite perkelimo transformacijos matricos 2-os eilutes elementus:")
  (setq M21 (getreal "\n1-ojo elemento reiksme: "))
  (setq M22 (getreal "2-ojo elemento reiksme: "))
  (setq M23 (getreal "3-ojo elemento reiksme: "))
(prompt "\nIveskite perkelimo transformacijos matricos 3-os eilutes elementus:")
  (setq M31 (getreal "\n1-ojo elemento reiksme: "))
  (setq M32 (getreal "2-ojo elemento reiksme: "))
  (setq M33 (getreal "3-ojo elemento reiksme: "))
(setq xxx1 (+ (* x1 M11) (* y1 M21) (* TX 1))) (setq yyy1 (+ (* x1 M12) (* y1 M22) (* TY 1)))
(setq xxx2 (+ (* x2 M11) (* y2 M21) (* TX 1))) (setq yyy2 (+ (* x2 M12) (* y2 M22) (* TY 1)))
(setq xxx3 (+ (* x3 M11) (* y3 M21) (* TX 1))) (setq yyy3 (+ (* x3 M12) (* y3 M22) (* TY 1)))
(command "color" "Red" )
(if (and (= xxx1 xx1) (= yyy1 yy1) (= xxx2 xx2) (= yyy2 yy2)(= xxx3 xx3)(= yyy3 yy3)
	 (= M31 TX) (= M32 TY) (= M33 1)) (setq rezultatas1 1) (setq rezultatas1 0))
(if (= rezultatas1 1)  (command "text" (list 2 17) 2.5 0 "TEISINGAI!")
                       (command "text" (list 2 17) 2.5 0 "KLAIDINGAI! Bandykite dar karta."))
(command "pline" (list xxx1 yyy1) "w" 0.2 0.2 (list xxx2 yyy2) (list xxx3 yyy3) "c")
(command "zoom" "e")
)
; pasukimo transformacijos matrica
(defun c:pasukimas(/ x1 y1 x2 y2 x3 y3 xx1 yy1 xx2 yy2 xx3 yy3 xxx1 yyy1 xxx2 yyy2 x y m11 m12 m13 m21 m22 m23 m31 m32 m33 TX TY pasukimass)
;(setq x1 0 y1 0 x2 8 y2 -4 x3 8 y3 4)
(command "color" "Red" )
(setq variantas2 (getint "\nNurodykite varianta - iveskite destytojo nurodyta numeri: "))
(setq pasukimass (rem variantas2 11))
  (if (= pasukimass 0) (setq x1  2 y1  2 x2   8 y2  1 x3   8 y3  3 xx1  2 yy1  2 xx2  3 yy2  8 xx3  1 yy3  8))
  (if (= pasukimass 1) (setq x1  4 y1  6 x2   3 y2  2 x3   5 y3  2 xx1  4 yy1  6 xx2  5 yy2 10 xx3  3 yy3 10))
  (if (= pasukimass 2) (setq x1 -4 y1  3 x2 -10 y2  2 x3 -10 y3  4 xx1 -4 yy1  3 xx2 -5 yy2  9 xx3 -3 yy3  9))
  (if (= pasukimass 3) (setq x1 -8 y1 -6 x2  -9 y2 -2 x3  -7 y3 -2 xx1 -8 yy1 -6 xx2 -4 yy2 -5 xx3 -4 yy3 -7))
  (if (= pasukimass 4) (setq x1  7 y1 -3 x2  11 y2 -2 x3  11 y3 -4 xx1  7 yy1 -3 xx2  3 yy2 -4 xx3  3 yy3 -2))
  (if (= pasukimass 5) (setq x1  7 y1 -3 x2  11 y2 -2 x3  11 y3 -4 xx1  7 yy1 -3 xx2  8 yy2 -7 xx3  6 yy3 -7))
  (if (= pasukimass 6) (setq x1  5 y1  6 x2   9 y2  7 x3   9 y3  5 xx1  5 yy1  6 xx2  1 yy2  5 xx3  1 yy3  7))
  (if (= pasukimass 7) (setq x1 -6 y1  4 x2  -7 y2  8 x3  -5 y3  8 xx1 -6 yy1  4 xx2 -2 yy2  5 xx3 -2 yy3  3))
  (if (= pasukimass 8) (setq x1 -6 y1 -3 x2  -2 y2 -2 x3  -2 y3 -4 xx1 -6 yy1 -3 xx2 -5 yy2 -7 xx3 -7 yy3 -7))
  (if (= pasukimass 9) (setq x1  2 y1 -3 x2   1 y2 -7 x3   3 y3 -7 xx1  2 yy1 -3 xx2  6 yy2 -4 xx3  6 yy3 -2))
  (if (= pasukimass 10) (setq x1  -6 y1 -3 x2   -7 y2 -7 x3   -5 y3 -7 xx1  -6 yy1 -3 xx2  -2 yy2 -4 xx3  -2 yy3 -2))
  ;(setq xx1 (+ x1 TX)  yy1 (+ y1 TX) xx2 (+ (* x2 P11) (* y2 P21)) yy2 (+ (* x2 P12) (* y2 P22))
	;xx3 (+ (* x3 P11) (* y3 P21)) yy3 (+ (* x3 P12) (* y3 P22)) )
(command "ucsicon" "off")  (command "limits" (list -13 -13) (list 13 13))
(command "zoom" "window" (list -13 -13) (list 13 13) )
(command "grid" 0.5) (command "grid" "on")
(command "snap" 0.5) (command "snap" "off") (setvar "osmode" 0)
(command "erase" "all" "") (command "color" "Red" )
(command "text" (list -13 12)  0.5 0 "Pasukimo transformacijos matrica");"Pasukimo apie koordinaciu pradzia transformacijos matrica")
(command "line" '(-10 0) '(10 0) "") (command "line" '(0 -10) '(0 10) "")
(command "pline" '(10 0) "w" 0.5 0 '(11 0) "")
(command "pline" '(0 10) "w" 0.5 0 '(0 11) "")
(setvar "pdmode" 2) (setvar "pdsize" -3)
(setq x -10) (setq y -10) (command "color" "Magenta" )
(command "point" (list x1 y1)) (command "point" (list xx1 yy1)) 
(repeat 20 (command "point" (list 0 y)(command "point" (list x 0))  )
  (setq x (+ x 1)) (setq y (+ y 1)))
  (setq x -10) (setq y -10) (command "color" "Blue" )
(repeat 11 (command "text" "j" "mc" (list -1 y) 0.5 0 X)
   (command "text" "j" "c" (list x -1) 0.5 0 y)
   (setq x (+ x 2)) (setq y (+ y 2)))
(command "line" (list x1 y1) (list x2 y2) (list x3 y3) "c") (command "color" "Green" )
(command "line" (list xx1 yy1) (list xx2 yy2) (list xx3 yy3) "c")
(command "zoom" "all") (command "color" "Red" ) ;(command "text" (list 5 1)  0.8 0 "Yra")
  (if (= pasukimass 0) (progn (command "text" (list 5 1.625) 0.8  0 "Yra") (command "text" (list 2.25 4.5) 0.6 90  "Reikia")))
  (if (= pasukimass 1) (progn (command "text" (list 3.5 4.5) 0.8  270 "Yra") (command "text" (list 4.25  7.5) 0.6  90  "Reikia")))
  (if (= pasukimass 2) (progn (command "text" (list -9  2.5) 0.8  0 "Yra") (command "text" (list -3.75  6) 0.6  90  "Reikia")))
  (if (= pasukimass 3) (progn (command "text" (list -7.5   -4.5) 0.8  90 "Yra") (command "text" (list -6.5 -6.25) 0.6  0  "Reikia")))
  (if (= pasukimass 4) (progn (command "text" (list 8.5  -3.5) 0.8  0 "Yra") (command "text" (list 3.5 -3.25) 0.6 0  "Reikia")))
  (if (= pasukimass 5) (progn (command "text" (list 8.5 -3.5) 0.8  0 "Yra") (command "text" (list 6.75 -4) 0.6 270  "Reikia")))
  (if (= pasukimass 6) (progn (command "text" (list 6.5 5.5) 0.8  0 "Yra") (command "text" (list 1.5 5.75) 0.6 0  "Reikia")))
  (if (= pasukimass 7) (progn (command "text" (list -5.5 5.5) 0.8  90 "Yra") (command "text" (list -5 3.625) 0.6 0  "Reikia")))
  (if (= pasukimass 8) (progn (command "text" (list -4.5  -3.5) 0.8  0 "Yra") (command "text" (list -6.25 -4) 0.6  270  "Reikia")))
  (if (= pasukimass 9) (progn (command "text" (list 1.5 -4.5) 0.8  270 "Yra") (command "text" (list 3  -3.25) 0.6  0  "Reikia")))
   (if (= pasukimass 10) (progn (command "text" (list -6.5 -4.5) 0.8  270 "Yra") (command "text" (list -5  -3.25) 0.6  0  "Reikia")))
(prompt "\nIveskite pasukimo apie taðkà (") (princ x1 ) (prompt ",") (princ y1) (prompt ") transformacijos matricos 1-os eilutes elementus:")
  (setq M11 (getreal "\n1-ojo elemento reiksme: "))
  (setq M12 (getreal "2-ojo elemento reiksme: "))
  (setq M13 (getreal "3-ojo elemento reiksme: "))
(prompt "\nIveskite pasukimo apie koordinaciu pradzia transformacijos matricos 2-os eilutes elementus:")
  (setq M21 (getreal "\n1-ojo elemento reiksme: "))
  (setq M22 (getreal "2-ojo elemento reiksme: "))
  (setq M23 (getreal "3-ojo elemento reiksme: "))
(prompt "\nIveskite pasukimo apie koordinaciu pradzia transformacijos matricos 3-os eilutes elementus:")
  (setq M31 (getreal "\n1-ojo elemento reiksme: "))
  (setq M32 (getreal "2-ojo elemento reiksme: "))
  (setq M33 (getreal "3-ojo elemento reiksme: "))
(setq xxx1 (+ (* x1 M11) (* y1 M21) (* 1 M31))) (setq yyy1 (+ (* x1 M12) (* y1 M22) (* 1 M32)))
(setq xxx2 (+ (* x2 M11) (* y2 M21) (* 1 M31))) (setq yyy2 (+ (* x2 M12) (* y2 M22) (* 1 M32)))
(setq xxx3 (+ (* x3 M11) (* y3 M21) (* 1 M31))) (setq yyy3 (+ (* x3 M12) (* y3 M22) (* 1 M32)))
(command "color" "Red" )
(if (and (= xxx1 xx1) (= yyy1 yy1) (= xxx2 xx2) (= yyy2 yy2)(= xxx3 xx3)(= yyy3 yy3)) (setq rezultatas2 1) (setq rezultatas2 0))
	; (= M31 0) (= M32 0) (= M33 1)) 
(if (= rezultatas2 1)   (command "text" (list -12 9) 2 0 "TEISINGAI!")
 			(command "text" (list -12 9) 2 0 "KLAIDINGAI! Bandykite dar karta."))
  (command "pline" (list xxx1 yyy1) "w" 0.2 0.2 (list xxx2 yyy2) (list xxx3 yyy3) "c")
(command "zoom" "e")
)
; masteliavimo-perkelimo transformacijos matrica
(defun c:mastelis()
;(/ x1 y1 x2 y2 x3 y3 x4 y4 xx1 yy1 xx2 yy2 xx3 yy3 xx4 yy4 xxx1 yyy1 xxx2 yyy2
;	    xxx4 yyy4 x y m11 m12 m13 m21 m22 m23 m31 m32 m33 SX SY masteliss)
(setq x1 2 y1 2 x2 4 y2 2 x3 4 y3 4 x4 2 y4 4)
(command "color" "Red" )
(setq variantas3 (getint "\nNurodykite varianta - iveskite destytojo nurodyta numeri: "))
(setq masteliss (rem variantas3 11))
(if (= masteliss 0) (setq SX 2 SY 3)) (if (= masteliss 1) (setq SX 3 SY 2))
(if (= masteliss 2) (setq SX 3 SY 1)) (if (= masteliss 3) (setq SX 4 SY 3))
;(setq xx1 (* x1 SX) yy1 (* y1 SY) xx2 (* x2 SX) yy2 (* y2 SY) xx3 (* x3 SX) yy3 (* y3 SY)
;      xx4 (* x4 SX) yy4 (* y4 SY))
(if (= masteliss 0) (setq XX1 4 YY1 6 XX2 8  YY2  6 XX3  8  YY3 12 XX4 4 YY4 12))
(if (= masteliss 1) (setq XX1 6 YY1 4 XX2 12 YY2  4 XX3  12 YY3 8  XX4 6 YY4 8))
(if (= masteliss 2) (setq XX1 6 YY1 2 XX2 12 YY2  2 XX3  12 YY3 4  XX4 6 YY4 4))
(if (= masteliss 3) (setq XX1 8 YY1 6 XX2 16 YY2  6 XX3 16  YY3 12 XX4 8 YY4 12))
(if (= masteliss 4) (setq XX1 9 YY1 6 XX2 17 YY2  6 XX3 17  YY3 12 XX4 9 YY4 12))
(if (= masteliss 5) (setq XX1 9 YY1 5 XX2 17 YY2  5 XX3 17  YY3 11 XX4 9 YY4 11))
(if (= masteliss 6) (setq XX1 10 YY1 6 XX2 18 YY2  6 XX3 18  YY3 12 XX4 10 YY4 12))
(if (= masteliss 7) (setq XX1 9 YY1 8 XX2 17 YY2  8 XX3 17  YY3 14 XX4 9 YY4 14))
(if (= masteliss 8) (setq XX1 7 YY1 6 XX2 15 YY2  6 XX3 15  YY3 12 XX4 7 YY4 12))
(if (= masteliss 9) (setq XX1 9 YY1 1 XX2 17 YY2  1 XX3 17  YY3 7 XX4 9 YY4 7))
(if (= masteliss 10) (setq XX1 7 YY1 3 XX2 15 YY2  3 XX3 15  YY3 8 XX4 7 YY4 8))
  
(command "ucsicon" "off")  (command "limits" (list -2 -2) (list 21 21))
(command "zoom" "window" (list -2 -2) (list 21 21) )
(command "grid" 1) (command "grid" "on")
(command "snap" 1) (command "snap" "off") (setvar "osmode" 0)
(command "erase" "all" "") (command "color" "Red" )
(command "text" (list -1 20)  0.8 0 "Mastelio transformacijos matrica")
(command "line" '(-1 0) '(20 0) "") (command "line" '(0 -1) '(0 20) "")
(command "pline" '(19 0) "w" 0.5 0 '(20 0) "")
(command "pline" '(0 19) "w" 0.5 0 '(0 20) "")
(setvar "pdmode" 2) (setvar "pdsize" -4)
(setq x 1) (setq y 1) (command "color" "Magenta" )
(command "point" (list x1 y1)) (command "point" (list xx1 yy1)) 
(repeat 18 (command "point" (list 0 y)(command "point" (list x 0))  )
  (setq x (+ x 1)) (setq y (+ y 1)))
  (setq x 2) (setq y 2) (command "color" "Blue" )
(repeat 9 (command "text" "j" "mc" (list -1 y) 0.5 0 X)
  (command "text" "j" "c" (list x -1) 0.5 0 y)
  (setq x (+ x 2)) (setq y (+ y 2)))
(command "line" (list x1 y1) (list x2 y2) (list x3 y3) (list x4 y4) "c")
(command "donut" 0 0.3 (list x1 y1) "")
(command "color" "Green")
(command "line" (list xx1 yy1) (list xx2 yy2) (list xx3 yy3) (list xx4 yy4) "c")
(command "color" "Red" )
(command "text" "j" "mc" (list (+ x1 1) (+ y1 1))  0.6 0 "Yra")
(command "text" "j" "a" (list (+ xx1 0.5) (+ yy1 0.7)) (list (- xx2 0.5) (+ yy1 0.7)) "Reikia" 1 0 )
(prompt "\nIveskite mastelio transformacijos matricos 1-os eilutes elementus:")
(setq M11 (getreal "\n1-ojo elemento reiksme: "))
(setq M12 (getreal "2-ojo elemento reiksme: "))
(setq M13 (getreal "3-ojo elemento reiksme: "))
(prompt "\nIveskite mastelio transformacijos matricos 2-os eilutes elementus:")
(setq M21 (getreal "\n1-ojo elemento reiksme: "))
(setq M22 (getreal "2-ojo elemento reiksme: "))
(setq M23 (getreal "3-ojo elemento reiksme: "))
(prompt "\nIveskite mastelio transformacijos matricos 3-os eilutes elementus:")
(setq M31 (getreal "\n1-ojo elemento reiksme: "))
(setq M32 (getreal "2-ojo elemento reiksme: "))
(setq M33 (getreal "3-ojo elemento reiksme: "))
;(setq xxx1 (* x1 M11)) (setq yyy1 (* y1 M22))
;(setq xxx2 (* x2 M11)) (setq yyy2 (* y2 M22))
;(setq xxx3 (* x3 M11)) (setq yyy3 (* y3 M22))
;(setq xxx4 (* x4 M11)) (setq yyy4 (* y4 M22))
;(command "color" "Red" )
;(if (and (= xxx1 xx1) (= yyy1 yy1) (= xxx2 xx2) (= yyy2 yy2)(= xxx3 xx3)(= yyy3 yy3)
;	 (= yyy4 yy4) (= M21 0) (= M12 0) (= M13 0)
;	 (= M31 0) (= M32 0) (= M33 1)) (setq rezultatas3 1) (setq rezultatas3 0))
(setq xxx1 (+ (* x1 M11) (* y1 M21) (* 1 M31 ))) (setq yyy1 (+ (* x1 M12) (* y1 M22) (* 1 M32)))
(setq xxx2 (+ (* x2 M11) (* y2 M21) (* 1 M31 ))) (setq yyy2 (+ (* x2 M12) (* y2 M22) (* 1 M32)))
(setq xxx3 (+ (* x3 M11) (* y3 M21) (* 1 M31 ))) (setq yyy3 (+ (* x3 M12) (* y3 M22) (* 1 M32)))
(setq xxx4 (+ (* x4 M11) (* y4 M21) (* 1 M31 ))) (setq yyy4 (+ (* x4 M12) (* y4 M22) (* 1 M32)))  
(command "color" "Red" )
(if (and (= xxx1 xx1) (= yyy1 yy1) (= xxx2 xx2) (= yyy2 yy2)(= xxx3 xx3)(= yyy3 yy3) (= xxx4 xx4)(= yyy4 yy4)
	 (= M33 1)) (setq rezultatas3 1) (setq rezultatas3 0))
  
(if (= rezultatas3 1)   (command "text" (list 2 17) 2.5 0 "TEISINGAI!")
		 	(command "text" (list 2 17) 2.5 0 "KLAIDINGAI! Bandykite dar karta."))
(command "pline" (list xxx1 yyy1) "w" 0.2 0.2 (list xxx2 yyy2) (list xxx3 yyy3)
	 (list xxx4 yyy4) "c")
(command "zoom" "e")
)
; sutapdintu transformaciju kompozicijos matrica
(defun c:kompozicija ()
(setq x1 2 y1 3 x2 4 y2 5 x3 4 y3 1)
(command "color" "Red" )
(setq variantas4 (getint "\nNurodykite varianta - iveskite destytojo nurodyta numeri: "))
(setq kompozicijaa (rem variantas4 11))
(if (= kompozicijaa 0) (setq XX1 4 YY1 8 XX2 2 YY2 4 XX3 2 YY3 12))
(if (= kompozicijaa 1) (setq XX1 9 YY1 5 XX2 5 YY2 3 XX3 5 YY3 7))
(if (= kompozicijaa 2) (setq XX1 10 YY1 4 XX2 6 YY2 6 XX3 14 YY3 6))
(if (= kompozicijaa 3) (setq XX1 10 YY1 4 XX2 14 YY2 2 XX3 6 YY3 2))
(if (= kompozicijaa 4) (setq XX1 9 YY1 8 XX2 11 YY2 4 XX3 7 YY3 4))
;(if (= kompozicijaa 5) (setq XX1 9 YY1 8 XX2 6 YY2 2 XX3 12 YY3 2))
(if (= kompozicijaa 5) (setq XX1 9 YY1 8 XX2 12 YY2 2 XX3 6 YY3 2)) 
(if (= kompozicijaa 6) (setq XX1 13 YY1 4 XX2 7 YY2 6 XX3 19 YY3 6))
(if (= kompozicijaa 7) (setq XX1 11 YY1 4 XX2 15 YY2 2 XX3 7 YY3 2))
(if (= kompozicijaa 8) (setq XX1 12 YY1 4 XX2 16 YY2 2 XX3 8 YY3 2))
(if (= kompozicijaa 9) (setq XX1 13 YY1 4 XX2 17 YY2 2 XX3 9 YY3 2))
(if (= kompozicijaa 10) (setq XX1 14 YY1 7 XX2 18 YY2 5 XX3 10 YY3 5)) 
(command "ucsicon" "off")  (command "limits" (list -2 -2) (list 21 21))
(command "zoom" "window" (list -2 -2) (list 21 21) )
(command "grid" 1) (command "grid" "on")
(command "snap" 1) (command "snap" "off") (setvar "osmode" 0)
(command "erase" "all" "") (command "color" "Red" )
(command "text" (list -2 20)  0.6 0 "Sutapdintu transformaciju kompozicijos matrica")
(command "line" '(-1 0) '(20 0) "") (command "line" '(0 -1) '(0 20) "")
(command "pline" '(19 0) "w" 0.5 0 '(20 0) "")
(command "pline" '(0 19) "w" 0.5 0 '(0 20) "")
(setvar "pdmode" 2) (setvar "pdsize" -4)
(setq x 1) (setq y 1) (command "color" "Magenta" )
(command "point" (list x1 y1)) (command "point" (list xx1 yy1)) 
(repeat 18 (command "point" (list 0 y)(command "point" (list x 0))  )
  (setq x (+ x 1)) (setq y (+ y 1)))
  (setq x 2) (setq y 2) (command "color" "Blue" )
(repeat 9 (command "text" "j" "mc" (list -1 y) 0.5 0 X)
  (command "text" "j" "c" (list x -1) 0.5 0 y)
  (setq x (+ x 2)) (setq y (+ y 2)))
(command "line" (list x1 y1) (list x2 y2) (list x3 y3) "c") (command "color" "Green")
(command "line" (list xx1 yy1) (list xx2 yy2) (list xx3 yy3) "c")
(command "color" "Red" )
(command "text" "j" "mc"(list (+ x1 2) y1)  0.8 0 "Yra")
(command "text" "j" "mc"(list (+ xx1 2) yy1)  0.6 0 "Reikia")
(prompt "\nIveskite sutapdintu transformaciju kompozicijos matricos 1-os eilutes elementus:")
  (setq M11 (getreal "   \n1-ojo elemento reiksme: "))
  (setq M12 (getreal "   2-ojo elemento reiksme: "))
  (setq M13 (getreal "   3-ojo elemento reiksme: "))
(prompt "\nIveskite sutapdintu transformaciju kompozicijos matricos 2-os eilutes elementus:")
  (setq M21 (getreal "   \n1-ojo elemento reiksme: "))
  (setq M22 (getreal "   2-ojo elemento reiksme: "))
  (setq M23 (getreal "   3-ojo elemento reiksme: "))
(prompt "\nIveskite sutapdintu transformaciju kompozicijos matricos 3-os eilutes elementus:")
  (setq M31 (getreal "   \n1-ojo elemento reiksme: "))
  (setq M32 (getreal "   2-ojo elemento reiksme: "))
  (setq M33 (getreal "   3-ojo elemento reiksme: "))
(setq xxx1 (+ (* x1 M11) (* y1 M21) (* 1 M31 ))) (setq yyy1 (+ (* x1 M12) (* y1 M22) (* 1 M32)))
(setq xxx2 (+ (* x2 M11) (* y2 M21) (* 1 M31 ))) (setq yyy2 (+ (* x2 M12) (* y2 M22) (* 1 M32)))
(setq xxx3 (+ (* x3 M11) (* y3 M21) (* 1 M31 ))) (setq yyy3 (+ (* x3 M12) (* y3 M22) (* 1 M32)))
(command "color" "Red" )
(if (and (= xxx1 xx1) (= yyy1 yy1) (= xxx2 xx2) (= yyy2 yy2)(= xxx3 xx3)(= yyy3 yy3)
	 (= M33 1)) (setq rezultatas4 1) (setq rezultatas4 0))
(if (= rezultatas4 1)  	(command "text" (list 2 17) 2.5 0 "TEISINGAI!")
		 	(command "text" (list 2 17) 2.5 0 "KLAIDINGAI! Bandykite dar karta."))
(command "pline" (list xxx1 yyy1) "w" 0.2 0.2 (list xxx2 yyy2) (list xxx3 yyy3) "c")
  (command "zoom" "e")
)

; atspindzio transformacijos matrica
(defun c:atspindys(/ x1 y1 x2 y2 x3 y3 x4 y4 xx1 yy1 xx2 yy2 xx3 yy3 xx4 yy4 xxx1 yyy1 xxx2 yyy2 xxx3 yyy3 xxx4 yyy4 x y m11 m12 m13 m21 m22 m23 m31 m32 m33 TX TY atspindyss)
(command "color" "Red" )
(setq variantas5 (getint "\nNurodykite varianta - iveskite destytojo nurodyta numeri: "))
(setq atspindyss (rem variantas5 11))
  (if (= atspindyss 0) (setq x1 2 y1 2 x2 5 y2 6 x3 4 y3 3 x4 5 y4 2 xx1 2 yy1 -2 xx2 5 yy2 -6 xx3 4 yy3 -3 xx4 5 yy4 -2))
  (if (= atspindyss 1) (setq x1 2 y1 2 x2 5 y2 6 x3 4 y3 3 x4 5 y4 2 xx1 -2 yy1 2 xx2 -5 yy2 6 xx3 -4 yy3 3 xx4 -5 yy4 2))
  (if (= atspindyss 2) (setq x1 2 y1 -2 x2 5 y2 -6 x3 4 y3 -3 x4 5 y4 -2 xx1 2 yy1 2 xx2 5 yy2 6 xx3 4 yy3 3 xx4 5 yy4 2))
  (if (= atspindyss 3) (setq x1 -2 y1 2 x2 -5 y2 6 x3 -4 y3 3 x4 -5 y4 2 xx1 2 yy1 2 xx2 5 yy2 6 xx3 4 yy3 3 xx4 5 yy4 2))
  (if (= atspindyss 4) (setq x1 -2 y1 2 x2 -5 y2 6 x3 -4 y3 3 x4 -5 y4 2 xx1 -2 yy1 -2 xx2 -5 yy2 -6 xx3 -4 yy3 -3 xx4 -5 yy4 -2))
  (if (= atspindyss 5) (setq x1 -2 y1 -2 x2 -5 y2 -6 x3 -4 y3 -3 x4 -5 y4 -2 xx1 -2 yy1 2 xx2 -5 yy2 6 xx3 -4 yy3 3 xx4 -5 yy4 2))
  (if (= atspindyss 6) (setq x1 -2 y1 -2 x2 -5 y2 -6 x3 -4 y3 -3 x4 -5 y4 -2 xx1 2 yy1 -2 xx2 5 yy2 -6 xx3 4 yy3 -3 xx4 5 yy4 -2))
  (if (= atspindyss 7) (setq x1 2 y1 -2 x2 5 y2 -6 x3 4 y3 -3 x4 5 y4 -2 xx1 -2 yy1 -2 xx2 -5 yy2 -6 xx3 -4 yy3 -3 xx4 -5 yy4 -2))
  (if (= atspindyss 8) (setq x1 2 y1 6 x2 5 y2 2 x3 4 y3 5 x4 5 y4 6 xx1 -2 yy1 6 xx2 -5 yy2 2 xx3 -4 yy3 5 xx4 -5 yy4 6))
  (if (= atspindyss 9) (setq x1 -2 y1 6 x2 -5 y2 2 x3 -4 y3 5 x4 -5 y4 6 xx1 2 yy1 6 xx2 5 yy2 2 xx3 4 yy3 5 xx4 5 yy4 6))
  (if (= atspindyss 10) (setq x1 -3 y1 -3 x2 -6 y2 -7 x3 -5 y3 -4 x4 -6 y4 -3 xx1 3 yy1 -3 xx2 6 yy2 -7 xx3 5 yy3 -4 xx4 6 yy4 -3))
  
(command "ucsicon" "off")  (command "limits" (list -13 -13) (list 13 13))
(command "zoom" "window" (list -13 -13) (list 13 13) )
(command "grid" 0.5) (command "grid" "on")
(command "snap" 0.5) (command "snap" "off") (setvar "osmode" 0)
(command "erase" "all" "") (command "color" "Red" )
(command "text" (list -13 12)  0.5 0 "Atspindzio transformacijos matrica")
(command "line" '(-10 0) '(10 0) "") (command "line" '(0 -10) '(0 10) "")
(command "pline" '(10 0) "w" 0.5 0 '(11 0) "")
(command "pline" '(0 10) "w" 0.5 0 '(0 11) "")
(setvar "pdmode" 2) (setvar "pdsize" -3)
(setq x -10) (setq y -10) (command "color" "Magenta" )
(command "point" (list x1 y1)) (command "point" (list xx1 yy1)) 
(repeat 20 (command "point" (list 0 y)(command "point" (list x 0))  )
  (setq x (+ x 1)) (setq y (+ y 1)))
  (setq x -10) (setq y -10) (command "color" "Blue" )
(repeat 11 (command "text" "j" "mc" (list -1 y) 0.5 0 X)
   (command "text" "j" "c" (list x -1) 0.5 0 y)
   (setq x (+ x 2)) (setq y (+ y 2)))
(command "line" (list x1 y1) (list x2 y2) (list x3 y3) (list x4 y4) "c") (command "color" "Green" )
(command "line" (list xx1 yy1) (list xx2 yy2) (list xx3 yy3) (list xx4 yy4) "c")
(command "zoom" "all") (command "color" "Red" ) 
  (if (= atspindyss 0) (progn (command "text" (list 5 1.625) 0.8  0 "Yra") (command "text" (list 3 -6.5) 0.6 90  "Reikia")))
  (if (= atspindyss 1) (progn (command "text" (list 5 1.625) 0.8  0 "Yra") (command "text" (list -8 2) 0.6 0  "Reikia")))
  (if (= atspindyss 2) (progn (command "text" (list 6 -6) 0.8  0 "Yra") (command "text" (list 6 6) 0.6 0  "Reikia")))
  (if (= atspindyss 3) (progn (command "text" (list -8 2) 0.8  0 "Yra") (command "text" (list 6 2) 0.6 0  "Reikia")))
  (if (= atspindyss 4) (progn (command "text" (list -8 2) 0.8  0 "Yra") (command "text" (list -8 -7) 0.6 0  "Reikia")))
  (if (= atspindyss 5) (progn (command "text" (list -8 -7) 0.8  0 "Yra") (command "text" (list -8 2) 0.6 0  "Reikia")))
  (if (= atspindyss 6) (progn (command "text" (list -8 -7) 0.8  0 "Yra") (command "text" (list 6 -7) 0.6 0  "Reikia")))
  (if (= atspindyss 7) (progn (command "text" (list 6 -7) 0.8  0 "Yra") (command "text" (list -8 -7) 0.6 0  "Reikia")))
  (if (= atspindyss 8) (progn (command "text" (list 6 2) 0.8  0 "Yra") (command "text" (list -8 2) 0.6 0  "Reikia")))
  (if (= atspindyss 9) (progn (command "text" (list -8 2) 0.8  0 "Yra") (command "text" (list 6 2) 0.6 0  "Reikia")))
  (if (= atspindyss 10) (progn (command "text" (list -9 -7) 0.8  0 "Yra") (command "text" (list 7 -7) 0.6 0  "Reikia")))
  
(prompt "\nIveskite atspindzio (") (princ x1 ) (prompt ",") (princ y1) (prompt ") transformacijos matricos 1-os eilutes elementus:")
  (setq M11 (getreal "\n1-ojo elemento reiksme: "))
  (setq M12 (getreal "2-ojo elemento reiksme: "))
  (setq M13 (getreal "3-ojo elemento reiksme: "))
(prompt "\nIveskite atspindzio transformacijos matricos 2-os eilutes elementus:")
  (setq M21 (getreal "\n1-ojo elemento reiksme: "))
  (setq M22 (getreal "2-ojo elemento reiksme: "))
  (setq M23 (getreal "3-ojo elemento reiksme: "))
(prompt "\nIveskite atspindzio transformacijos matricos 3-os eilutes elementus:")
  (setq M31 (getreal "\n1-ojo elemento reiksme: "))
  (setq M32 (getreal "2-ojo elemento reiksme: "))
  (setq M33 (getreal "3-ojo elemento reiksme: "))
(setq xxx1 (+ (* x1 M11) (* y1 M21) (* 1 M31))) 
(setq yyy1 (+ (* x1 M12) (* y1 M22) (* 1 M32)))

(setq xxx2 (+ (* x2 M11) (* y2 M21) (* 1 M31))) 
(setq yyy2 (+ (* x2 M12) (* y2 M22) (* 1 M32)))

(setq xxx3 (+ (* x3 M11) (* y3 M21) (* 1 M31))) 
(setq yyy3 (+ (* x3 M12) (* y3 M22) (* 1 M32)))

(setq xxx4 (+ (* x4 M11) (* y4 M21) (* 1 M31))) 
(setq yyy4 (+ (* x4 M12) (* y4 M22) (* 1 M32)))

(command "color" "Red" )

(if (and (= xxx1 xx1) (= yyy1 yy1) (= xxx2 xx2) (= yyy2 yy2)(= xxx3 xx3)(= yyy3 yy3) (= xxx4 xx4) (= yyy4 yy4)) 
	(setq rezultatas5 1) 
	(setq rezultatas5 0)
)

(if (= rezultatas5 1)   
	(command "text" (list -12 9) 2 0 "TEISINGAI!")
 	(command "text" (list -12 9) 2 0 "KLAIDINGAI! Bandykite dar karta.")
)

(command "pline" (list xxx1 yyy1) "w" 0.2 0.2 (list xxx2 yyy2) (list xxx3 yyy3) (list xxx4 yyy4)"c")
(command "zoom" "e")
)

; slyties transformacijos matrica
(defun c:slytis(/ x1 y1 x2 y2 x3 y3 x4 y4 xx1 yy1 xx2 yy2 xx3 yy3 xx4 yy4 xxx1 yyy1 xxx2 yyy2 xxx3 yyy3 xxx4 yyy4 x y m11 m12 m13 m21 m22 m23 m31 m32 m33 TX TY slytiss)
(command "color" "Red" )
(setq variantas6 (getint "\nNurodykite varianta - iveskite destytojo nurodyta numeri: "))
(setq slytiss (rem variantas6 11))
  (if (= slytiss 0) (setq x1 2 y1 2 x2 2 y2 4 x3 5 y3 4 x4 5 y4 2 xx1 -5 yy1 2 xx2 -3 yy2 4 xx3 0 yy3 4 xx4 -2 yy4 2))
  (if (= slytiss 1) (setq x1 2 y1 2 x2 2 y2 4 x3 5 y3 4 x4 5 y4 2 xx1 -5 yy1 2 xx2 -7 yy2 4 xx3 -4 yy3 4 xx4 -2 yy4 2))
  (if (= slytiss 2) (setq x1 2 y1 2 x2 2 y2 4 x3 5 y3 4 x4 5 y4 2 xx1 -5 yy1 2 xx2 -5 yy2 4 xx3 -2 yy3 7 xx4 -2 yy4 5))
  (if (= slytiss 3) (setq x1 2 y1 2 x2 2 y2 4 x3 5 y3 4 x4 5 y4 2 xx1 -5 yy1 2 xx2 -5 yy2 4 xx3 -2 yy3 1 xx4 -2 yy4 -1))
  (if (= slytiss 4) (setq x1 2 y1 -4 x2 2 y2 -2 x3 5 y3 -2 x4 5 y4 -4 xx1 -5 yy1 -4 xx2 -3 yy2 -2 xx3 0 yy3 -2 xx4 -2 yy4 -4))
  (if (= slytiss 5) (setq x1 2 y1 -4 x2 2 y2 -2 x3 5 y3 -2 x4 5 y4 -4 xx1 -5 yy1 -4 xx2 -7 yy2 -2 xx3 -4 yy3 -2 xx4 -2 yy4 -4))
  (if (= slytiss 6) (setq x1 2 y1 -4 x2 2 y2 -2 x3 5 y3 -2 x4 5 y4 -4 xx1 -5 yy1 -4 xx2 -5 yy2 -2 xx3 -2 yy3 1 xx4 -2 yy4 -1))
  (if (= slytiss 7) (setq x1 2 y1 -4 x2 2 y2 -2 x3 5 y3 -2 x4 5 y4 -4 xx1 -5 yy1 -4 xx2 -5 yy2 -2 xx3 -2 yy3 -5 xx4 -2 yy4 -7))
  (if (= slytiss 8) (setq x1 2 y1 -4 x2 2 y2 -2 x3 5 y3 -2 x4 5 y4 -4 xx1 -5 yy1 2 xx2 -3 yy2 4 xx3 0 yy3 4 xx4 -2 yy4 2))
  (if (= slytiss 9) (setq x1 2 y1 -4 x2 2 y2 -2 x3 5 y3 -2 x4 5 y4 -4 xx1 -5 yy1 2 xx2 -7 yy2 4 xx3 -4 yy3 4 xx4 -2 yy4 2))
  (if (= slytiss 10) (setq x1 2 y1 -4 x2 2 y2 -2 x3 5 y3 -2 x4 5 y4 -4 xx1 -6 yy1 2 xx2 -8 yy2 4 xx3 -5 yy3 4 xx4 -3 yy4 2))

(command "ucsicon" "off")  (command "limits" (list -13 -13) (list 13 13))
(command "zoom" "window" (list -13 -13) (list 13 13) )
(command "grid" 0.5) (command "grid" "on")
(command "snap" 0.5) (command "snap" "off") (setvar "osmode" 0)
(command "erase" "all" "") (command "color" "Red" )
(command "text" (list -13 12)  0.5 0 "Slyties transformacijos matrica")
(command "line" '(-10 0) '(10 0) "") (command "line" '(0 -10) '(0 10) "")
(command "pline" '(10 0) "w" 0.5 0 '(11 0) "")
(command "pline" '(0 10) "w" 0.5 0 '(0 11) "")
(setvar "pdmode" 2) (setvar "pdsize" -3)
(setq x -10) (setq y -10) (command "color" "Magenta" )
(command "point" (list x1 y1)) (command "point" (list xx1 yy1)) 
(repeat 20 (command "point" (list 0 y)(command "point" (list x 0))  )
  (setq x (+ x 1)) (setq y (+ y 1)))
  (setq x -10) (setq y -10) (command "color" "Blue" )
(repeat 11 (command "text" "j" "mc" (list -1 y) 0.5 0 X)
   (command "text" "j" "c" (list x -1) 0.5 0 y)
   (setq x (+ x 2)) (setq y (+ y 2)))
(command "line" (list x1 y1) (list x2 y2) (list x3 y3) (list x4 y4) "c") (command "color" "Green" )
(command "line" (list xx1 yy1) (list xx2 yy2) (list xx3 yy3) (list xx4 yy4) "c")
(command "zoom" "all") (command "color" "Red" ) 
  (if (= slytiss 0) (progn (command "text" (list 5.5 1.625) 0.8  0 "Yra") (command "text" (list -8 1) 0.6 0  "Reikia")))
  (if (= slytiss 1) (progn (command "text" (list 5.5 1.625) 0.8  0 "Yra") (command "text" (list -8 1) 0.6 0  "Reikia")))
  (if (= slytiss 2) (progn (command "text" (list 5.5 1.625) 0.8  0 "Yra") (command "text" (list -8 1) 0.6 0  "Reikia")))
  (if (= slytiss 3) (progn (command "text" (list 5.5 1.625) 0.8  0 "Yra") (command "text" (list -8 1) 0.6 0  "Reikia")))
  (if (= slytiss 4) (progn (command "text" (list 5.5 -4.375) 0.8  0 "Yra") (command "text" (list -8 -5) 0.6 0  "Reikia")))
  (if (= slytiss 5) (progn (command "text" (list 5.5 -4.375) 0.8  0 "Yra") (command "text" (list -8 -5) 0.6 0  "Reikia")))
  (if (= slytiss 6) (progn (command "text" (list 5.5 -4.375) 0.8  0 "Yra") (command "text" (list -8 -5) 0.6 0  "Reikia")))
  (if (= slytiss 7) (progn (command "text" (list 5.5 -4.375) 0.8  0 "Yra") (command "text" (list -8 -5) 0.6 0  "Reikia")))
  (if (= slytiss 8) (progn (command "text" (list 5.5 -4.375) 0.8  0 "Yra") (command "text" (list -8 1) 0.6 0  "Reikia")))
  (if (= slytiss 9) (progn (command "text" (list 5.5 -4.375) 0.8  0 "Yra") (command "text" (list -8 1) 0.6 0  "Reikia")))
  (if (= slytiss 10) (progn (command "text" (list 5.5 -4.375) 0.8  0 "Yra") (command "text" (list -10 2) 0.6 0  "Reikia")))

(prompt "\nIveskite slyties (") (princ x1 ) (prompt ",") (princ y1) (prompt ") transformacijos matricos 1-os eilutes elementus:")
  (setq M11 (getreal "\n1-ojo elemento reiksme: "))
  (setq M12 (getreal "2-ojo elemento reiksme: "))
  (setq M13 (getreal "3-ojo elemento reiksme: "))
(prompt "\nIveskite slyties transformacijos matricos 2-os eilutes elementus:")
  (setq M21 (getreal "\n1-ojo elemento reiksme: "))
  (setq M22 (getreal "2-ojo elemento reiksme: "))
  (setq M23 (getreal "3-ojo elemento reiksme: "))
(prompt "\nIveskite slyties transformacijos matricos 3-os eilutes elementus:")
  (setq M31 (getreal "\n1-ojo elemento reiksme: "))
  (setq M32 (getreal "2-ojo elemento reiksme: "))
  (setq M33 (getreal "3-ojo elemento reiksme: "))
(setq xxx1 (+ (* x1 M11) (* y1 M21) (* 1 M31))) 
(setq yyy1 (+ (* x1 M12) (* y1 M22) (* 1 M32)))

(setq xxx2 (+ (* x2 M11) (* y2 M21) (* 1 M31))) 
(setq yyy2 (+ (* x2 M12) (* y2 M22) (* 1 M32)))

(setq xxx3 (+ (* x3 M11) (* y3 M21) (* 1 M31))) 
(setq yyy3 (+ (* x3 M12) (* y3 M22) (* 1 M32)))

(setq xxx4 (+ (* x4 M11) (* y4 M21) (* 1 M31))) 
(setq yyy4 (+ (* x4 M12) (* y4 M22) (* 1 M32)))

(command "color" "Red" )

(if (and (= xxx1 xx1) (= yyy1 yy1) (= xxx2 xx2) (= yyy2 yy2)(= xxx3 xx3)(= yyy3 yy3) (= xxx4 xx4) (= yyy4 yy4)) 
	(setq rezultatas6 1) 
	(setq rezultatas6 0)
)

(if (= rezultatas6 1)   
	(command "text" (list -12 9) 2 0 "TEISINGAI!")
 	(command "text" (list -12 9) 2 0 "KLAIDINGAI! Bandykite dar karta.")
)

(command "pline" (list xxx1 yyy1) "w" 0.2 0.2 (list xxx2 yyy2) (list xxx3 yyy3) (list xxx4 yyy4)"c")
(command "zoom" "e")
)

; rezultatu patikra
(defun c:patikra (/ atgarsis)
(textscr)
(setq atgarsis (getvar "cmdecho")) (setvar "cmdecho" 0)
 (command "color" "Red" ) (princ "  \nVarianto Nr= ") (princ variantas1)
(if ( and (= rezultatas1 rezultatas2  rezultatas3 rezultatas4 rezultatas5 rezultatas6 1)
	  (= variantas1 variantas2 variantas3 variantas4 variantas5 variantas6))
  (princ "\nVisos transformacijos atliktos teisingai  -   DARBAS UZSKAITOMAS"))
(if (not (and (= variantas1 variantas2 variantas3 variantas4 variantas5 variantas6)))
  (princ "\nUzduociu variantai skirtingi arba ne visi atlikti - DARBAS NEUZSKAITOMAS. Bandykite dar karta."))
(if (and (= rezultatas1 1) (= variantas1 variantas1))
  (princ "\n  1. Perkelimo   transformacijos matrica sudaryta  TEISINGAI")
  (princ "\nPerkelimo   transformacijos matrica sudaryta  KLAIDINGAI. Bandykite dar karta."))
(if (and (= rezultatas2 1) (= variantas2 variantas1))
  (princ "\n  2. Pasukimo    transformacijos matrica sudaryta  TEISINGAI")
  (princ "\nPasukimo    transformacijos matrica sudaryta  KLAIDINGAI. Bandykite dar karta."))  
(if (and (= rezultatas3 1) (= variantas3 variantas1))
  (princ "\n  3. Masteliavimo transformacijos matrica sudaryta  TEISINGAI")
  (princ "\nMasteliavimo transformacijos matrica sudaryta  KLAIDINGAI. Bandykite dar karta."))
(if (and (= rezultatas4 1) (= variantas4 variantas1))
  (princ "\n  4. Transformaciju kompozicijos matrica sudaryta  TEISINGAI")
  (princ "\nTransformaciju kompozicijos matrica sudaryta  KLAIDINGAI. Bandykite dar karta"))
(if (and (= rezultatas5 1) (= variantas5 variantas1))
  (princ "\n  5. Atspindzio  transformacijos matrica sudaryta  TEISINGAI")
  (princ "\nAtspindzio  transformacijos matrica sudaryta  KLAIDINGAI. Bandykite dar karta"))
(if (and (= rezultatas6 1) (= variantas6 variantas1))
  (princ "\n  6. Slyties     transformacijos matrica sudaryta  TEISINGAI\n")
  (princ "\nSlyties     transformacijos matrica sudaryta  KLAIDINGAI. Bandykite dar karta\n"))
(setvar "cmdecho" atgarsis)
)
